from enclosure_runtime import output_dir, source_path, artifact_path, document, new_document
import FreeCAD as App, FreeCADGui as Gui, Part, Mesh, MeshPart, os, json, math
OUT=output_dir('domed-mounted')
os.makedirs(OUT,exist_ok=True)
src=document('Integrated_PuckSide')
d=new_document('Domed_Mounted_Pendant');d.Label='Domed pendant — removable internal carriers'
V=App.Vector
def box(x,y,z,w,l,h):return Part.makeBox(w,l,h,V(x,y,z))
def cyl(x,y,z,r,h):return Part.makeCylinder(r,h,V(x,y,z))
def fuse(parts):
 s=parts[0]
 for p in parts[1:]:s=s.fuse(p)
 return s.removeSplitter()
def obj(name,s,color):
 o=d.addObject('Part::Feature',name);o.Shape=s;o.ViewObject.ShapeColor=color;return o
mounts=[(-12,-17),(12,-17),(0,22)]
lidmounts=[(-23,-10),(23,10),(0,25.5)]
components={o.Name:o.Shape.copy() for o in src.ComponentReferences.Group}
button=box(21.7,-8.3,9.7,4.5,6.6,6.6)
wireholes=[box(-21,-4,7,6,14,13),box(10.5,-5,7,1.5,11,13)]
# The new base is copied; original documents and flat exports are never modified.
basebits=[src.Base.Shape.copy(),box(-12.25,-12.25,1.4,24.5,24.5,0.5)]
for x,y in mounts:basebits.append(cyl(x,y,1.4,2.2,5.9))
# Rounded battery locators, 0.4 mm nominal lateral clearance; no pouch-clamping snap hooks.
for sign in [-1,1]:
 for along in [-10.5,10.5]:
  basebits.append(cyl(sign*13.25,along,1.4,0.6,3.8))
  basebits.append(cyl(along,sign*13.25,1.4,0.6,3.8))
motorseat=cyl(18,-5,1.4,5.9,3.8).cut(cyl(18,-5,1.9,5.25,4))
motorseat=motorseat.cut(box(-12.65,-12.65,1.9,25.3,25.3,6)).cut(box(16.3,-0.5,1.8,3.4,5,4))
basebits.append(motorseat)
# Connector locating fence; antenna gets removable insulating adhesive rather than a pressure clamp.
basebits += [box(13.3,8,1.4,0.4,8,3),box(20.3,8,1.4,0.6,8,3)]
base=fuse(basebits)
for x,y in mounts:base=base.cut(cyl(x,y,2.5,0.8,5.2))
# Removable lower shelf also forms the battery's non-compressing overhead restraint.
lowerbits=[cyl(0,0,7.3,26,0.9)]
for x,y in mounts:lowerbits.append(cyl(x,y,8.2,2.2,5))
# Board edge fences, keeping the USB/card-facing edge open.
for x in [-9.95,9.3]:lowerbits += [box(x,-22,8.2,0.65,19,1),box(x,2,8.2,0.65,16,1)]
lowerbits += [box(-8,-1.1,8.2,16,0.6,1),box(-8,19.3,8.2,16,0.6,1)]
for x in [12.1,21.3]:lowerbits.append(box(x,0,8.2,0.6,8,1))
lowerbits += [box(13,-0.9,8.2,8,0.6,1),box(13,8.3,8.2,8,0.6,1)]
# Downward retainers stop motor and connector lift; thin foam takes up the 0.3 mm gap.
lowerbits += [box(15,-6,5.2,6,2,2.2),box(15,10,6.2,4,4,1.2)]
lower=fuse(lowerbits)
# Thread thin insulating retaining bands through these slots. Standard thick cable ties will not fit the stack.
for x,y in [(-10.8,-12),(10.2,-12),(-10.8,7),(10.2,7),(11.9,3),(21.9,3)]:
 lower=lower.cut(box(x,y,7,0.7,3,2.5))
# Upper carrier with circular seats, SD side fences and standoffs for the removable retainer.
upperbits=[cyl(0,0,13.2,26,1)]
for x,y in mounts:upperbits.append(cyl(x,y,14.2,2.2,3.5))
for x,y,r in [(-9,16,7),(9,16,7),(0,6,5)]:
 upperbits.append(cyl(x,y,14.2,r,0.2))
 seat=cyl(x,y,14.2,r+1.0,3.5).cut(cyl(x,y,14.2,r+0.3,3.6))
 if r==5:seat=seat.cut(box(4.8,4.3,14.2,5,3.4,4))
 else:seat=seat.cut(box(x-9,14.3,14.3,18,3.4,3.6))
 upperbits.append(seat)
upperbits += [box(-9.95,-23,14.2,0.65,22,2),box(9.3,-23,14.2,0.65,22,2),box(-8,0.3,14.2,16,0.6,2)]
upper=fuse(upperbits).cut(cyl(0,0,17.1,1.95,2))
# Retainer overlaps microphone/speaker rims, not their centers; SD gets a bridge with a soft pad.
retainer=cyl(0,0,17.7,24.2,1)
for x,y,r in [(-9,16,6),(9,16,6),(0,6,4)]:retainer=retainer.cut(cyl(x,y,17.6,r,1.3))
for y,l in [(-27,19),(-5,5.3)]:retainer=retainer.cut(box(-9.3,y,17.6,18.6,l,1.3))
retainer=retainer.fuse(cyl(0,0,17.5,1.8,1.2)).cut(cyl(0,0,17,1.15,2)).removeSplitter()
# Keep port/button reservations, screw bosses and wiring routes clear on all three removable pieces.
parts=[]
for shape in [lower,upper,retainer]:
 for x,y in mounts:shape=shape.cut(cyl(x,y,7,1.1,13))
 for x,y in lidmounts:shape=shape.cut(cyl(x,y,7,2.6,13))
 for opening in wireholes+[button]:shape=shape.cut(opening)
 parts.append(shape.removeSplitter())
lower,upper,retainer=parts
# A 6 mm spherical dome; existing seam and locating lip remain unchanged.
rise=6.0;radius=(28*28+rise*rise)/(2*rise);center=V(0,0,20.4+rise-radius)
cap=Part.makeSphere(radius,center).common(cyl(0,0,19,28,8)).cut(Part.makeSphere(radius-1.4,center))
rim=src.Lid.Shape.cut(cyl(0,0,19,26,10))
lid=rim.fuse(cap).removeSplitter()
for x,y in lidmounts:
 lid=lid.cut(cyl(x,y,17,1.1,12)).cut(cyl(x,y,20.1,2.1,9))
for x in [-9,9]:lid=lid.cut(cyl(x,16,17,0.8,12))
for x in [-2.5,0,2.5]:
 for y in [3.5,6,8.5]:lid=lid.cut(cyl(x,y,17,0.6,12))
lid=lid.cut(cyl(0,0,17,1.3,12)).removeSplitter()
guide=cyl(0,0,18.5,1,7.9)
# Loosen only the new male dovetails, preserving the latch shoulder and flat exterior face.
def railprism(points):
 vertices=[V(x,-50,z) for x,z in points];vertices.append(vertices[0])
 return Part.Face(Part.makePolygon(vertices)).extrude(V(0,100,0))
def rear_map(shape):
 shape=Part.makeCompound(shape.Solids).mirror(V(),V(0,0,1));shape.translate(V(0,-19,1.4));return shape
allowed=rear_map(railprism([(-11.4,1.75),(11.4,1.75),(9.6,4.1),(-9.6,4.1)]))
railcut=box(-35,-75,-2.7,70,150,2.7).cut(allowed)
flush=src.FlushInsert.Shape.cut(railcut).removeSplitter()
clip=src.ClipInsert.Shape.cut(railcut).removeSplitter()
flank_clearance=(12-(1.75-1.4)*2/3-11.4)/math.sqrt(1+(2/3)**2)
assert flank_clearance>=0.3
printed=[]
for name,shape,color in [('Base',base,(0.65,0.73,0.8)),('DomedLid',lid,(0.65,0.73,0.8)),('LowerCarrier',lower,(0.22,0.65,0.55)),('UpperCarrier',upper,(0.3,0.55,0.85)),('TopRetainer',retainer,(0.8,0.6,0.3)),('FlushInsert',flush,(0.25,0.75,0.58)),('ClipInsert',clip,(0.25,0.35,0.5)),('LightGuide',guide,(0.3,0.95,0.55))]:
 o=obj(name,shape,color);printed.append(o)
refs=d.addObject('App::DocumentObjectGroup','ComponentReferences')
for original in src.ComponentReferences.Group:
 o=obj(original.Name,original.Shape.copy(),original.ViewObject.ShapeColor);refs.addObject(o)
# Visual hardware references: not STL parts. Shafts intentionally engage the smaller plastic pilots.
hardware=d.addObject('App::DocumentObjectGroup','RequiredHardware')
for i,(x,y) in enumerate(mounts):
 o=obj('CarrierScrew'+str(i+1),fuse([cyl(x,y,2.7,1,16),cyl(x,y,18.7,1.8,1.5)]),(0.65,0.65,0.65));hardware.addObject(o)
# Nonconductive band envelopes show actual retention, and clearance beneath the shelf/above the boards.
bands=[('XIAOBand',-10.6,10.7,-12,7.1,12.9),('AmplifierBand',-10.6,10.7,7,7.1,11.4),('DriverBand',12.1,22.4,3,7.1,11.4)]
for name,x1,x2,y,z1,z2 in bands:
 band=box(x1,y,z1,x2-x1,3,z2-z1).cut(box(x1+0.15,y-0.1,z1+0.15,x2-x1-0.3,3.2,z2-z1-0.3))
 o=obj(name,band,(0.9,0.75,0.2));hardware.addObject(o)
# Required soft pads; these are purchased/cut foam, not rigid printed clamps.
for name,x,y,z,w,l,h in [('MotorPad',15,-6,4.9,6,2,0.3),('ConnectorPad',15,10,5.9,4,4,0.3),('SDPad',-7,-8,17.2,14,3,0.5)]:
 o=obj(name,box(x,y,z,w,l,h),(0.4,0.4,0.4));hardware.addObject(o)
for name,x,y,outer,inner in [('MicLeftPad',-9,16,6.9,6),('MicRightPad',9,16,6.9,6),('SpeakerRimPad',0,6,4.9,4)]:
 pad=cyl(x,y,17.4,outer,0.3).cut(cyl(x,y,17.3,inner,0.5)).cut(cyl(0,0,17.3,1.95,0.6))
 o=obj(name,pad,(0.4,0.4,0.4));hardware.addObject(o)
# Check geometry before any printable exports.
issues=[]
for o in printed:
 if not o.Shape.isValid() or len(o.Shape.Solids)!=1:issues.append([o.Name,'invalid_or_disconnected',len(o.Shape.Solids)])
 for name,shape in components.items():
  v=o.Shape.common(shape).Volume
  if v>0.001:issues.append([o.Name,name,v])
for i,a in enumerate(printed):
 for b in printed[i+1:]:
  if {a.Name,b.Name}=={'FlushInsert','ClipInsert'}:continue
  v=a.Shape.common(b.Shape).Volume
  if v>0.001:issues.append([a.Name,b.Name,v])
# Check hardware clearance outside the designed pilot engagement.
for o in hardware.Group:
 for p in printed:
  if o.Name.startswith('CarrierScrew') and p.Name=='Base':continue
  v=o.Shape.common(p.Shape).Volume
  if v>0.001:issues.append([o.Name,p.Name,v])
 for name,shape in components.items():
  v=o.Shape.common(shape).Volume
  if v>0.001:issues.append([o.Name,name,v])
for reference in document('Measured_PuckSide').WireReservations.Group:
 for o in printed:
  v=o.Shape.common(reference.Shape).Volume
  if v>0.001:issues.append([o.Name,reference.Name,v])
print('GEOMETRY ISSUES',json.dumps(issues))
assert not issues,issues
# Recheck latch retention and released withdrawal with the looser male profile.
proto=document('Modular_Mount_Prototype')
hook=proto.LatchHook.Shape.copy();hook.translate(V(-0.95,0,0))
released=flush.cut(rear_map(proto.LatchBeam.Shape)).cut(rear_map(proto.LatchHook.Shape))
released=released.fuse(rear_map(proto.ReleasedBeamProxy.Shape)).fuse(rear_map(hook)).removeSplitter()
locked=flush.copy();locked.translate(V(0,-0.8,0))
assert base.common(locked).Volume>0.01,'Latch no longer retains insert'
for distance in [0,0.1,0.25,0.5,0.8,1,1.5,2,3,4,6,8,12,16,20,24,28,32,36,40,48,56,64]:
 for moving in [released.copy(),clip.cut(flush)]:
  moving.translate(V(0,-distance,0))
  assert moving.common(base).Volume<0.001,('Released insert interference',distance)
# Removing the lid does not release the carriers: three independent M2x16 screws retain them.
# Once those screws and the next layer are removed, every carrier lifts vertically clear of the base.
for o in [d.LowerCarrier,d.UpperCarrier,d.TopRetainer]:
 for dz in [0.2,1,3,6,10,18,25]:
  moving=o.Shape.copy();moving.translate(V(0,0,dz))
  assert moving.common(base).Volume<0.001,(o.Name,'base extraction',dz)
checks=[]
for idx,o in enumerate(printed,1):
 s=o.Shape.copy()
 if o.Name in ['FlushInsert','ClipInsert']:s.rotate(V(),V(0,1,0),90)
 # Dome stays upright on its rim; supports may be needed under the inner spherical roof.
 bb=s.BoundBox;s.translate(V(-bb.XMin,-bb.YMin,-bb.ZMin))
 mesh=MeshPart.meshFromShape(Shape=s,LinearDeflection=0.05,AngularDeflection=0.15,Relative=False)
 assert mesh.isSolid() and not mesh.hasNonManifolds() and not mesh.hasSelfIntersections(),o.Name
 path=OUT+'/%02d-%s.stl'%(idx,o.Name);mesh.write(path)
 loaded=Mesh.Mesh(path);assert loaded.isSolid() and not loaded.hasNonManifolds() and not loaded.hasSelfIntersections(),path
 checks.append({'part':o.Name,'single_valid_solid':True,'closed_reimported_mesh':True,'facets':loaded.CountFacets})
for o in refs.Group+hardware.Group+[d.LowerCarrier,d.UpperCarrier,d.TopRetainer,d.ClipInsert]:o.ViewObject.Visibility=False
d.recompute();d.saveAs(OUT+'/Domed-Mounted-Pendant.FCStd')
Part.export([o for o in printed if o.Name!='ClipInsert'],OUT+'/Domed-Mounted-Flush-Assembly.step')
report={'body_diameter_mm':56,'dome_rise_mm':6,'flush_total_thickness_mm':30,'clip_total_thickness_mm':37,'carrier_mounts_xy_mm':mounts,'carrier_screws':'3 x M2x16, plastic-compatible thread form; verify physical pilot fit','battery_top_clearance_mm':0.4,'issues':issues,'carrier_vertical_extraction_clear':True,'parts':checks,'status':'CAD-checked mounting prototype; physical tolerances, SD envelope, foam preload, RF and acoustics unverified'}
report.update({'dovetail_minimum_flank_clearance_mm':flank_clearance,'dovetail_floor_clearance_mm':0.35,'dovetail_mouth_clearance_per_side_mm':0.4,'latch_retention_checked':True,'released_dovetail_path_checked':True})
with open(OUT+'/verification.json','w') as f:json.dump(report,f,indent=2)
Gui.activeDocument().activeView().viewAxonometric()
print(json.dumps(report))
