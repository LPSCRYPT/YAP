from enclosure_runtime import output_dir, source_path, artifact_path, document, new_document
import FreeCAD as App, FreeCADGui as Gui, Part, Mesh, json
OUT=output_dir('mounting')
checks=[]
for key in ['PuckFace','PuckSide','Capsule']:
 d=document('Measured_'+key)
 d.LED.Placement.Base=App.Vector(0,0,17.5)
 d.LED.Label='CENTRAL STATUS LED — mounting envelope'
 hole=d.getObject('LEDPort');hole.Placement.Base.x=0;hole.Placement.Base.y=0;hole.Radius=1.3
 lens=d.addObject('Part::Cylinder','CentralLightGuide');lens.Radius=1; lens.Height=1.9;lens.Placement.Base=App.Vector(0,0,18.5)
 lens.setExpression('Height','Parameters.Height-18.5')
 lens.Label='CENTRAL LIGHT GUIDE — clear/translucent insert, 0.3 mm radial clearance'
 lens.ViewObject.ShapeColor=(0.35,0.95,0.6)
 d.Components.addObject(lens)
 clearance=d.addObject('Part::Box','CentralLEDWireSpace');clearance.Length=2;clearance.Width=2;clearance.Height=1.1;clearance.Placement.Base=App.Vector(-1,-1,17.4)
 clearance.Label='Central LED solder/wire allowance — provisional 2 x 2 x 1.1 mm'
 clearance.ViewObject.Visibility=False
 d.WearableMountNotes.set('A10','LED relocated to exact front-face center. 2.6 mm opening, 2 mm light guide. Confirm actual LED solder/wire envelope.')
 d.WearableMountNotes.set('A11','Central LED assembly sits above the SD holder; clearance is based on provisional SD dimensions.')
 d.recompute()
 assert d.Lid.Shape.isValid() and len(d.Lid.Shape.Solids)==1
 components=list(d.Components.Group)
 problems=[]
 for a in [d.LED,lens]:
  for b in [d.WearableBase,d.Lid,d.ClothingClip]+[o for o in components if o!=a]:
   volume=a.Shape.common(b.Shape).Volume
   if volume>0.001:problems.append([a.Name,b.Name,volume])
 for b in [d.WearableBase,d.Lid]+[o for o in components if o not in [d.LED,lens]]:
  assert clearance.Shape.common(b.Shape).Volume<0.001,(key,'LED wiring allowance',b.Name)
 assert not problems,problems
 d.LED.ViewObject.Visibility=True;lens.ViewObject.Visibility=True
 d.save()
 Part.export([d.WearableBase,d.Lid,d.ClothingClip,lens],OUT+'/Measured-'+key+'-Wearable.step')
 Mesh.export([d.Lid],OUT+'/Measured-'+key+'-Lid.stl')
 Mesh.export([lens],OUT+'/Measured-'+key+'-CentralLightGuide.stl')
 checks.append({'design':key,'central_LED_xy_mm':[0,0],'LED_port_diameter_mm':2.6,'lightguide_diameter_mm':2,'interferences':problems})
comparison=new_document('Wearable_Mount_Comparison');comparison.Label='Wearable mounts — front and rear / central LED'
for key,x,title in [('PuckFace',0,'A / front button'),('PuckSide',90,'B / side button'),('Capsule',180,'C / capsule')]:
 src=document('Measured_'+key)
 for rear,y in [(False,100),(True,0)]:
  group=comparison.addObject('App::Part',key+('Rear' if rear else 'Front'));group.Label=title+(' / rear clip' if rear else ' / front')
  for original in [src.WearableBase,src.Lid,src.ClothingClip]+list(src.Components.Group):
   o=comparison.addObject('Part::Feature',group.Name+'_'+original.Name);o.Shape=original.Shape.copy();o.Label=original.Label;o.ViewObject.ShapeColor=original.ViewObject.ShapeColor;o.ViewObject.Transparency=0;group.addObject(o)
  group.Placement=App.Placement(App.Vector(x,y,0),App.Rotation(App.Vector(0,1,0),180 if rear else 0))
  note=comparison.addObject('App::Annotation',group.Name+'Caption');note.LabelText=[title,'REAR: removable clip' if rear else 'FRONT: central LED + necklace eye'];note.Position=App.Vector(x-28,y-42,0);note.ViewObject.FontSize=14;note.ViewObject.TextColor=(0.95,0.95,0.95)
notes=comparison.addObject('Spreadsheet::Sheet','AttachmentNotes')
for i,text in enumerate(['Snapshots of editable Measured_* sources. Original comparison remains open.',
 'Necklace eye bore 4.4 mm; use breakaway cord. Strength untested.',
 'Rear clip mount: two M2 x 4 screws, 14 mm spacing. Do not use longer screws without checking battery clearance.',
 'Removable clip grip and fatigue untested. PETG prototype, not a validated production clip.',
 '20.4 mm case body; 22.4 mm with mounting pad, 27.4 mm with clip installed.',
 'Front LED now centered on all three variants; nominal 2 mm optical insert in a 2.6 mm port.'],1):notes.set('A%d'%i,text)
comparison.recompute();App.setActiveDocument(comparison.Name);Gui.activeDocument().activeView().viewAxonometric();Gui.updateGui()
comparison.saveAs(OUT+'/Wearable-Mount-Comparison.FCStd')
with open(OUT+'/central-led-checks.json','w') as f:json.dump(checks,f,indent=2)
print(json.dumps({'LED_checks':checks,'comparison':comparison.FileName}))
